FME workspace Overall Map creator.fmw

Parameters:
- SourceDataset_TIFF = /Users/joe/Documents/GitHub/CADW/data/Raw/wales_lidar_dtm_1m_32bit_cog.tif   # Source TIFF (Tagged Image File Format) File(s)
- Minecraft_name = Wales_DTM   # Minecraft file name
- DestDataset_FFS = /Users/joe/Documents/GitHub/CADW/data/Raw/DTM_pointcloud.ffs   # Destination FME Feature Store (FFS) File
- SourceDataset_FFS = /Users/joe/Documents/GitHub/CADW/data/Raw/DTM_pointcloud.ffs   # Source FME Feature Store (FFS) File(s)

Readers:
- TIFF_1: TIFF from $(SourceDataset_TIFF)
- FFS_2: FFS from $(SourceDataset_FFS)

Writers:
- FFS_1: FFS to $(DestDataset_FFS)

TIFF (reader TIFF_1) [off]
    -> Scaler [off]
Scaler [off]
    RASTER_SCALING = Extents
    SCALE_ORIGIN = 0,0
    TEXT_LOC_ONLY = Location and Size
    XSCALE = 0.001
    YSCALE = 0.001
    ZSCALE = 0.01
    SCALED -> PointCloudCombiner [off]
PointCloudCombiner [off]
    ACCUM_ATTRS_NAME = Yes
    EXTRACT_RASTER_NODATA_NAME = No
    SPACING = 1
    -> DTM Pointcloud (writer FFS_1) [off]
DTM Pointcloud (writer FFS_1) [off]
DTM Pointcloud (reader FFS_2)
    -> Scaler_2
Scaler_2
    RASTER_SCALING = Extents
    SCALE_ORIGIN = 0,0
    TEXT_LOC_ONLY = Location and Size
    XSCALE = 0.5
    YSCALE = 0.5
    ZSCALE = 0.75
    SCALED -> PointCloudThinner
PointCloudThinner
    INTERVAL = 100
    THINNED -> PointCloudComponentAdder
PointCloudComponentAdder
    COMPONENTS_TO_ADD = blockID,UInt32,2,blockData,UInt32,0
    -> Offsetter
Offsetter
    MODE = Cartesian Coordinate
    XOFF = 0
    YOFF = 0
    ZOFF = 10
    OFFSET -> FeatureWriter_2 [Offset]

Bookmark: Writes Minecraft file
FeatureWriter_2
    DATASET = /Users/joe/Library/Application Support/minecraft/saves
    DATASET_ATTR = _dataset
    FEATURE_TYPE_LIST_ATTR = _feature_types
    FORMAT = MINECRAFT
    MINECRAFT_BIOME = 1
    MINECRAFT_CENTER_POINT_CLOUD = yes
    MINECRAFT_COORDINATE_SYSTEM_GRANULARITY = FEATURE
    MINECRAFT_DESTINATION_DATASETTYPE_VALIDATION = Yes
    MINECRAFT_FILL_BLOCK = 1
    MINECRAFT_FILL_UNDER = yes
    MINECRAFT_GENERATOR_NAME = flat
    MINECRAFT_GENERATOR_OPTIONS = 2;7,2x3,2;1;
    MINECRAFT_POPULATE_TERRAIN = yes
    SELECTED_PORTS = Offset
    TOTAL_FEATURES_WRITTEN_ATTR = _total_features_written
    SUMMARY -> AttributeManager_5

Bookmark: Old Minecraft Writer
AttributeManager_5
    ATTR_TABLE:
      SET_TO output_location = /Users/joe/Library/Application\ Support/minecraft/saves/$(Minecraft_name)
      SET_TO text_line_data = #Removes old overviewer folder if it exists
        rm -r /Users/joe/Pictures/Overviewer/$(Minecraft_name)

        #Runs Overviewer
        /Users/joe/miniconda3/bin/python /Users/joe/Documents/GitHub/BlockBuilders_Experimental_Gitlab/Utilities/Reader_Writer/Overviewer/overviewer.py @Value(output_location) /Users/joe/Pictures/Overviewer/$(Minecraft_name)

        #Opens the result
        open /Users/joe/Pictures/Overviewer/$(Minecraft_name)/index.html
      REMOVE _feature_types{}.count
      REMOVE _feature_types{}.name
      REMOVE _dataset
      REMOVE _total_features_written
    -> FeatureWriter_5 [text_line]
FeatureWriter_5
    DATASET = /Users/joe/Documents/GitHub/CADW/functions/writer/run.sh
    DATASET_ATTR = _dataset
    FEATURE_TYPE_LIST_ATTR = _feature_types
    FORMAT = TEXTLINE
    TEXTLINE_COORDINATE_SYSTEM_GRANULARITY = FEATURE
    TEXTLINE_DESTINATION_DATASETTYPE_VALIDATION = Yes
    TEXTLINE_ENCODING = UTF-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    SUMMARY -> Logger_2
Logger_2
    LOG_FEATURE = NONE
    MAXFEATS = 20
    MESSAGE:
      Run this in the terminal:

      @Value(_dataset)
    SEVERITY = ERROR
